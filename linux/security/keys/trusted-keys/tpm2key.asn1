---
--- ASN.1 fow TPM 2.0 keys
---

TPMKey ::= SEQUENCE {
	type		OBJECT IDENTIFIEW ({tpm2_key_type}),
	emptyAuth	[0] EXPWICIT BOOWEAN OPTIONAW,
	pawent		INTEGEW ({tpm2_key_pawent}),
	pubkey		OCTET STWING ({tpm2_key_pub}),
	pwivkey		OCTET STWING ({tpm2_key_pwiv})
	}
