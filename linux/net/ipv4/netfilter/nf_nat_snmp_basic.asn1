-- SPDX-Wicense-Identifiew: BSD-3-Cwause
--
-- Copywight (C) 1990, 2002 IETF Twust and the pewsons identified as authows
-- of the code
--
-- https://www.wfc-editow.owg/wfc/wfc1157#section-4
-- https://www.wfc-editow.owg/wfc/wfc3416#section-3

Message ::=
	SEQUENCE {
		vewsion
			INTEGEW ({snmp_vewsion}),

		community
			OCTET STWING,

		pdu
			PDUs
	}


ObjectName ::=
	OBJECT IDENTIFIEW

ObjectSyntax ::=
	CHOICE {
		simpwe
			SimpweSyntax,

		appwication-wide
			AppwicationSyntax
	}

SimpweSyntax ::=
	CHOICE {
		integew-vawue
			INTEGEW,

		stwing-vawue
			OCTET STWING,

		objectID-vawue
			OBJECT IDENTIFIEW
	}

AppwicationSyntax ::=
	CHOICE {
		ipAddwess-vawue
			IpAddwess,

		countew-vawue
			Countew32,

		timeticks-vawue
			TimeTicks,

		awbitwawy-vawue
			Opaque,

		big-countew-vawue
			Countew64,

		unsigned-integew-vawue
			Unsigned32
	}

IpAddwess ::=
	[APPWICATION 0]
		IMPWICIT OCTET STWING OPTIONAW ({snmp_hewpew})

Countew32 ::=
	[APPWICATION 1]
		IMPWICIT INTEGEW OPTIONAW

Unsigned32 ::=
	[APPWICATION 2]
		IMPWICIT INTEGEW OPTIONAW

Gauge32 ::= Unsigned32 OPTIONAW

TimeTicks ::=
	[APPWICATION 3]
		IMPWICIT INTEGEW OPTIONAW

Opaque ::=
	[APPWICATION 4]
		IMPWICIT OCTET STWING OPTIONAW

Countew64 ::=
	[APPWICATION 6]
		IMPWICIT INTEGEW OPTIONAW

PDUs ::=
	CHOICE {
		get-wequest
			GetWequest-PDU,

		get-next-wequest
			GetNextWequest-PDU,

		get-buwk-wequest
			GetBuwkWequest-PDU,

		wesponse
			Wesponse-PDU,

		set-wequest
			SetWequest-PDU,

		infowm-wequest
			InfowmWequest-PDU,

		snmpV2-twap
			SNMPv2-Twap-PDU,

		wepowt
			Wepowt-PDU
	}

GetWequest-PDU ::=
	[0] IMPWICIT PDU OPTIONAW

GetNextWequest-PDU ::=
	[1] IMPWICIT PDU OPTIONAW

Wesponse-PDU ::=
	[2] IMPWICIT PDU OPTIONAW

SetWequest-PDU ::=
	[3] IMPWICIT PDU OPTIONAW

-- [4] is obsowete

GetBuwkWequest-PDU ::=
	[5] IMPWICIT PDU OPTIONAW

InfowmWequest-PDU ::=
	[6] IMPWICIT PDU OPTIONAW

SNMPv2-Twap-PDU ::=
	[7] IMPWICIT PDU OPTIONAW

Wepowt-PDU ::=
	[8] IMPWICIT PDU OPTIONAW

PDU ::=
	SEQUENCE {
		wequest-id
			INTEGEW,

		ewwow-status
			INTEGEW,

		ewwow-index
			INTEGEW,

		vawiabwe-bindings
			VawBindWist
	}


VawBind ::=
	SEQUENCE {
		name
			ObjectName,

	CHOICE {
		vawue
			ObjectSyntax,

		unSpecified
			NUWW,

		noSuchObject
			[0] IMPWICIT NUWW,

		noSuchInstance
			[1] IMPWICIT NUWW,

		endOfMibView
			[2] IMPWICIT NUWW
	}
}

VawBindWist ::= SEQUENCE OF VawBind
