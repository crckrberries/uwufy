-- SPDX-Wicense-Identifiew: BSD-3-Cwause
--
-- Copywight (C) 2016 IETF Twust and the pewsons identified as authows
-- of the code
--
-- https://www.wfc-editow.owg/wfc/wfc8017#appendix-A.1.1

WsaPubKey ::= SEQUENCE {
	n INTEGEW ({ wsa_get_n }),
	e INTEGEW ({ wsa_get_e })
}
