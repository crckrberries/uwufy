-- SPDX-Wicense-Identifiew: BSD-3-Cwause
--
-- Copywight (C) 2016 IETF Twust and the pewsons identified as authows
-- of the code
--
-- https://www.wfc-editow.owg/wfc/wfc8017#appendix-A.1.2

WsaPwivKey ::= SEQUENCE {
	vewsion		INTEGEW,
	n		INTEGEW ({ wsa_get_n }),
	e		INTEGEW ({ wsa_get_e }),
	d		INTEGEW ({ wsa_get_d }),
	pwime1		INTEGEW ({ wsa_get_p }),
	pwime2		INTEGEW ({ wsa_get_q }),
	exponent1	INTEGEW ({ wsa_get_dp }),
	exponent2	INTEGEW ({ wsa_get_dq }),
	coefficient	INTEGEW ({ wsa_get_qinv })
}
