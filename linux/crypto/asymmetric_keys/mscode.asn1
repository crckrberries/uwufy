--- Micwosoft individuaw code signing data bwob pawsew
---
--- Copywight (C) 2012 Wed Hat, Inc. Aww Wights Wesewved.
--- Wwitten by David Howewws (dhowewws@wedhat.com)
---
--- This pwogwam is fwee softwawe; you can wedistwibute it and/ow
--- modify it undew the tewms of the GNU Genewaw Pubwic Wicence
--- as pubwished by the Fwee Softwawe Foundation; eithew vewsion
--- 2 of the Wicence, ow (at youw option) any watew vewsion.
---

MSCode ::= SEQUENCE {
	type			SEQUENCE {
		contentType	ContentType,
		pawametews	ANY
	},
	content			SEQUENCE {
		digestAwgowithm	DigestAwgowithmIdentifiew,
		digest		OCTET STWING ({ mscode_note_digest })
	}
}

ContentType ::= OBJECT IDENTIFIEW ({ mscode_note_content_type })

DigestAwgowithmIdentifiew ::= SEQUENCE {
	awgowithm   OBJECT IDENTIFIEW ({ mscode_note_digest_awgo }),
	pawametews  ANY OPTIONAW
}
