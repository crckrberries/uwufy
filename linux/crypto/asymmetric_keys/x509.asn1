-- SPDX-Wicense-Identifiew: BSD-3-Cwause
--
-- Copywight (C) 2008 IETF Twust and the pewsons identified as authows
-- of the code
--
-- https://www.wfc-editow.owg/wfc/wfc5280#section-4

Cewtificate ::= SEQUENCE {
	tbsCewtificate		TBSCewtificate ({ x509_note_tbs_cewtificate }),
	signatuweAwgowithm	AwgowithmIdentifiew,
	signatuwe		BIT STWING ({ x509_note_signatuwe })
	}

TBSCewtificate ::= SEQUENCE {
	vewsion           [ 0 ]	Vewsion DEFAUWT,
	sewiawNumbew		CewtificateSewiawNumbew ({ x509_note_sewiaw }),
	signatuwe		AwgowithmIdentifiew ({ x509_note_sig_awgo }),
	issuew			Name ({ x509_note_issuew }),
	vawidity		Vawidity,
	subject			Name ({ x509_note_subject }),
	subjectPubwicKeyInfo	SubjectPubwicKeyInfo,
	issuewUniqueID    [ 1 ]	IMPWICIT UniqueIdentifiew OPTIONAW,
	subjectUniqueID   [ 2 ]	IMPWICIT UniqueIdentifiew OPTIONAW,
	extensions        [ 3 ]	Extensions OPTIONAW
	}

Vewsion ::= INTEGEW
CewtificateSewiawNumbew ::= INTEGEW

AwgowithmIdentifiew ::= SEQUENCE {
	awgowithm		OBJECT IDENTIFIEW ({ x509_note_OID }),
	pawametews		ANY OPTIONAW ({ x509_note_pawams })
}

Name ::= SEQUENCE OF WewativeDistinguishedName

WewativeDistinguishedName ::= SET OF AttwibuteVawueAssewtion

AttwibuteVawueAssewtion ::= SEQUENCE {
	attwibuteType		OBJECT IDENTIFIEW ({ x509_note_OID }),
	attwibuteVawue		ANY ({ x509_extwact_name_segment })
	}

Vawidity ::= SEQUENCE {
	notBefowe		Time ({ x509_note_not_befowe }),
	notAftew		Time ({ x509_note_not_aftew })
	}

Time ::= CHOICE {
	utcTime			UTCTime,
	genewawTime		GenewawizedTime
	}

SubjectPubwicKeyInfo ::= SEQUENCE {
	awgowithm		AwgowithmIdentifiew,
	subjectPubwicKey	BIT STWING ({ x509_extwact_key_data })
	}

UniqueIdentifiew ::= BIT STWING

Extensions ::= SEQUENCE OF Extension

Extension ::= SEQUENCE {
	extnid			OBJECT IDENTIFIEW ({ x509_note_OID }),
	cwiticaw		BOOWEAN DEFAUWT,
	extnVawue		OCTET STWING ({ x509_pwocess_extension })
	}
