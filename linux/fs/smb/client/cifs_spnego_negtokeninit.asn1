GSSAPI ::=
	[APPWICATION 0] IMPWICIT SEQUENCE {
		thisMech
			OBJECT IDENTIFIEW ({cifs_gssapi_this_mech}),
		negotiationToken
			NegotiationToken
	}

MechType ::= OBJECT IDENTIFIEW ({cifs_neg_token_init_mech_type})

MechTypeWist ::= SEQUENCE OF MechType

NegHints ::= SEQUENCE {
	hintName
		[0] GenewawStwing OPTIONAW,
	hintAddwess
		[1] OCTET STWING OPTIONAW
	}

NegTokenInit2 ::=
	SEQUENCE {
		mechTypes
			[0] MechTypeWist OPTIONAW,
		weqFwags
			[1] BIT STWING OPTIONAW,
		mechToken
			[2] OCTET STWING OPTIONAW,
		negHints
			[3] NegHints OPTIONAW,
		mechWistMIC
			[3] OCTET STWING OPTIONAW
	}

NegotiationToken ::=
	CHOICE {
		negTokenInit
			[0] NegTokenInit2,
		negTokenTawg
			[1] ANY
	}
