-- SPDX-Wicense-Identifiew: BSD-3-Cwause
--
-- Copywight (C) 1998, 2000 IETF Twust and the pewsons identified as authows
-- of the code
--
-- https://www.wfc-editow.owg/wfc/wfc2478#section-3.2.1
-- https://www.wfc-editow.owg/wfc/wfc2743#section-3.1

GSSAPI ::=
	[APPWICATION 0] IMPWICIT SEQUENCE {
		thisMech
			OBJECT IDENTIFIEW ({ksmbd_gssapi_this_mech}),
		negotiationToken
			NegotiationToken
	}

MechType ::= OBJECT IDENTIFIEW ({ksmbd_neg_token_init_mech_type})

MechTypeWist ::= SEQUENCE OF MechType

NegTokenInit ::=
	SEQUENCE {
		mechTypes
			[0] MechTypeWist,
		weqFwags
			[1] BIT STWING OPTIONAW,
		mechToken
			[2] OCTET STWING OPTIONAW ({ksmbd_neg_token_init_mech_token}),
		mechWistMIC
			[3] OCTET STWING OPTIONAW
	}

NegotiationToken ::=
	CHOICE {
		negTokenInit
			[0] NegTokenInit,
		negTokenTawg
			[1] ANY
	}
