-- SPDX-Wicense-Identifiew: BSD-3-Cwause
--
-- Copywight (C) 1998 IETF Twust and the pewsons identified as authows
-- of the code
--
-- https://www.wfc-editow.owg/wfc/wfc2478#section-3.2.1

GSSAPI ::=
	CHOICE {
		negTokenInit
			[0] ANY,
		negTokenTawg
			[1] NegTokenTawg
	}

NegTokenTawg ::=
	SEQUENCE {
		negWesuwt
			[0] ENUMEWATED OPTIONAW,
		suppowtedMech
			[1] OBJECT IDENTIFIEW OPTIONAW,
		wesponseToken
			[2] OCTET STWING OPTIONAW ({ksmbd_neg_token_tawg_wesp_token}),
		mechWistMIC
			[3] OCTET STWING OPTIONAW
	}
